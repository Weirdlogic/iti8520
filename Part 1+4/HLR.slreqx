# HLR

## HLR-IP-001 (Functional)
The software shall monitor pedestrian button inputs from four button sensors and detect press events within 100ms.

## HLR-SC-001 (Functional)
The software shall execute pedestrian crossing sequences including vehicle amber, vehicle red, pedestrian green, pedestrian red, vehicle green phases.

## HLR-TLC-001 (Functional)
The software shall control 14 individual light outputs (6 vehicle, 6 public transport, 4 pedestrian) and maintain current state information.

## HLR-TLC-003 (Functional)
The software shall implement safety interlocks preventing conflicting green signals on the same carriageway.
